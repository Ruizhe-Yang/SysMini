package Ecore{
	private import ScalarValues::*;
	private import Base::*;
	
	
	attribute def EString :> String;
	attribute def EObject :> Anything;
	attribute def EBoolean :> Boolean;
	attribute def EInt :> Integer;
	attribute def EFloat :> Real;
	attribute def BaseElement :> Anything;
}
